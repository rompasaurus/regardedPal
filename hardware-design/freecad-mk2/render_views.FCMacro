"""
Render Views — comprehensive render set for Dilder Rev 2 Mk2.

Run with:  freecad render_views.FCMacro
Or specify a file:
    DILDER_FCSTD="/path/to/MyFile.FCStd" freecad render_views.FCMacro

If DILDER_FCSTD is not set, opens the default Dilder_Rev2_Mk2.FCStd.
Output: ../renders/var-*.png and comp-*.png

Updated 2026-05-01: comprehensive re-render for piezo, IMU, anchor pad iteration.
"""

import os, sys, time
import FreeCAD as App
import FreeCADGui as Gui

MACRO_DIR = os.path.dirname(os.path.abspath(__file__))
FCSTD_PATH = os.environ.get("DILDER_FCSTD",
    os.path.join(MACRO_DIR, "Dilder_Rev2_Mk2.FCStd"))
RENDER_DIR = os.path.normpath(os.path.join(MACRO_DIR, "..", "renders"))

W, H = 1920, 1440
BG = "Transparent"

doc = App.openDocument(FCSTD_PATH)
Gui.ActiveDocument = Gui.getDocument(doc.Name)
view = Gui.ActiveDocument.activeView()


def all_objects():
    return [o for o in doc.Objects if hasattr(o, "ViewObject")]


def show(names):
    """Show the named objects, hide all others."""
    show_set = set(names)
    for o in all_objects():
        try:
            o.ViewObject.Visibility = (o.Name in show_set)
        except Exception:
            pass
    Gui.updateGui()


def show_all_except(hidden):
    h = set(hidden)
    for o in all_objects():
        try:
            o.ViewObject.Visibility = (o.Name not in h)
        except Exception:
            pass
    Gui.updateGui()


def set_cover_transparency(t):
    for o in all_objects():
        if o.Name == "TopCover":
            try:
                o.ViewObject.Transparency = t
            except Exception:
                pass


def save(name, axometric=True, fit=True):
    if axometric:
        try:
            Gui.SendMsgToActiveView("ViewIsometric")
        except Exception:
            pass
    if fit:
        Gui.SendMsgToActiveView("ViewFit")
    Gui.updateGui()
    time.sleep(0.05)
    out = os.path.join(RENDER_DIR, name)
    view.saveImage(out, W, H, BG)
    print(f"  wrote {out}")


def view_top():
    Gui.SendMsgToActiveView("ViewTop")
    Gui.SendMsgToActiveView("ViewFit")

def view_front():
    Gui.SendMsgToActiveView("ViewFront")
    Gui.SendMsgToActiveView("ViewFit")

def view_rear():
    Gui.SendMsgToActiveView("ViewRear")
    Gui.SendMsgToActiveView("ViewFit")

def view_left():
    Gui.SendMsgToActiveView("ViewLeft")
    Gui.SendMsgToActiveView("ViewFit")

def view_right():
    Gui.SendMsgToActiveView("ViewRight")
    Gui.SendMsgToActiveView("ViewFit")

def view_bottom():
    Gui.SendMsgToActiveView("ViewBottom")
    Gui.SendMsgToActiveView("ViewFit")


# ── Setup ──
set_cover_transparency(40)
os.makedirs(RENDER_DIR, exist_ok=True)
print(f"Rendering to {RENDER_DIR} ...")

# =====================================================================
# SECTION 1 — FULL ASSEMBLY (all components, transparent cover)
# =====================================================================

# 01 — Hero isometric
show_all_except([])
save("var-01-hero-iso.png")

# 02 — Top-down translucent
view_top()
save("var-02-top-translucent.png", axometric=False, fit=False)

# 03 — Front elevation
view_front()
save("var-03-front-elevation.png", axometric=False, fit=False)

# 04 — Side stack (left)
view_left()
save("var-04-side-left.png", axometric=False, fit=False)

# 05 — Side stack (right)
view_right()
save("var-05-side-right.png", axometric=False, fit=False)

# 06 — Rear elevation
view_rear()
save("var-06-rear-elevation.png", axometric=False, fit=False)

# =====================================================================
# SECTION 2 — COVER REMOVED (internals visible)
# =====================================================================

# 07 — Cover removed iso
show_all_except(["TopCover", "Thumbpiece"])
save("var-07-cover-removed-iso.png")

# 08 — Cover removed top
view_top()
save("var-08-cover-removed-top.png", axometric=False, fit=False)

# =====================================================================
# SECTION 3 — INDIVIDUAL BODIES
# =====================================================================

# 09 — Cradle + batteries + clips iso
show_all_except([
    "TopCover", "BasePlate", "Pico2W_Board", "Pico2W_Headers",
    "JoystickPCB", "Thumbpiece", "TP4056_Module",
    "EInkDisplay_Module", "EInkDisplay_Panel",
    "Piezo_Brass", "Piezo_Ceramic", "IMU_Module",
    "Solar_Frame", "Solar_Cells", "Solar_Wire_Plus", "Solar_Wire_Minus"])
save("var-09-cradle-batt-clips-iso.png")

# 10 — Cradle + batteries top
view_top()
save("var-10-cradle-batt-clips-top.png", axometric=False, fit=False)

# 11 — Pico + sensors on base plate
show(["BasePlate", "Piezo_Brass", "Piezo_Ceramic", "IMU_Module"])
save("var-11-pico-sensors-on-base.png")

# 12 — Baseplate top (sensors visible)
view_top()
save("var-12-baseplate-sensors-top.png", axometric=False, fit=False)

# 13 — Baseplate sensors iso
save("var-13-baseplate-sensors-iso.png")

# 14 — Baseplate bottom (solar panel)
show(["BasePlate", "Solar_Frame", "Solar_Cells",
      "Solar_Wire_Plus", "Solar_Wire_Minus"])
view_bottom()
save("var-14-baseplate-bottom.png", axometric=False, fit=False)

# 15 — Baseplate top (bare)
show(["BasePlate"])
view_top()
save("var-15-baseplate-top-bare.png", axometric=False, fit=False)

# 16 — Cradle bottom
show(["AAACradle"])
view_bottom()
save("var-16-cradle-bottom.png", axometric=False, fit=False)

# 17 — Cover bottom (anchor pad visible)
show(["TopCover"])
set_cover_transparency(0)
view_bottom()
save("var-17-cover-bottom.png", axometric=False, fit=False)

# 18 — Cover bottom iso (anchor pad)
save("var-18-cover-anchor-iso.png")

set_cover_transparency(40)

# =====================================================================
# SECTION 4 — DETAIL CLOSE-UPS
# =====================================================================

# 19 — Joystick + thumbpiece detail
show_all_except([])
save("var-19-joystick-detail.png")

# 20 — Joystick aligned top
view_top()
save("var-20-joystick-aligned-top.png", axometric=False, fit=False)

# 21 — Thumbpiece hero (85% transparent cover)
show_all_except([])
set_cover_transparency(85)
save("var-21-thumbpiece-hero.png")
set_cover_transparency(40)

# 22 — Display detail
show_all_except([])
save("var-22-display-detail.png")

# =====================================================================
# SECTION 5 — EXPLODED VIEWS
# =====================================================================

show_all_except([])
# Stash placements
saved = {}
for o in all_objects():
    if o.Name in ("TopCover", "AAACradle", "BasePlate", "Thumbpiece"):
        saved[o.Name] = App.Placement(o.Placement)

# Explode along Z
offsets = {"TopCover": 30, "Thumbpiece": 40, "AAACradle": 0, "BasePlate": -25}
for nm, dz in offsets.items():
    obj = doc.getObject(nm)
    if obj:
        p = App.Placement(saved.get(nm, obj.Placement))
        p.Base = p.Base + App.Vector(0, 0, dz)
        obj.Placement = p
doc.recompute()

# 23 — Exploded iso
save("var-23-exploded-iso.png")

# 24 — Exploded front
view_front()
save("var-24-exploded-front.png", axometric=False, fit=False)

# 25 — Exploded top
view_top()
save("var-25-exploded-top.png", axometric=False, fit=False)

# Restore placements
for nm, p in saved.items():
    obj = doc.getObject(nm)
    if obj:
        obj.Placement = p
doc.recompute()

# =====================================================================
# SECTION 6 — ASSEMBLED (opaque cover)
# =====================================================================

# 26 — Assembled iso (opaque cover)
show_all_except([])
set_cover_transparency(0)
save("var-26-assembled-opaque-iso.png")

# 27 — Assembled front (opaque)
view_front()
save("var-27-assembled-opaque-front.png", axometric=False, fit=False)

set_cover_transparency(40)

# =====================================================================
# SECTION 7 — PER-COMPONENT ISOLATED RENDERS (for design doc)
# =====================================================================

# Base plate — iso + top + bottom
show(["BasePlate"])
save("comp-baseplate-iso.png")
view_top()
save("comp-baseplate-top.png", axometric=False, fit=False)
view_bottom()
save("comp-baseplate-bottom.png", axometric=False, fit=False)

# AAA Cradle — iso + top + bottom
show(["AAACradle"])
save("comp-cradle-iso.png")
view_top()
save("comp-cradle-top.png", axometric=False, fit=False)
view_bottom()
save("comp-cradle-bottom.png", axometric=False, fit=False)

# Top Cover — iso (transparent) + bottom (opaque, shows anchor)
show(["TopCover"])
set_cover_transparency(40)
save("comp-cover-iso.png")
set_cover_transparency(0)
save("comp-cover-iso-opaque.png")
view_bottom()
save("comp-cover-bottom.png", axometric=False, fit=False)
view_top()
save("comp-cover-top.png", axometric=False, fit=False)
set_cover_transparency(40)

# Thumbpiece — iso
show(["Thumbpiece"])
save("comp-thumbpiece-iso.png")

# Joystick PCB — iso
show(["JoystickPCB"])
save("comp-joystick-pcb-iso.png")

# Pico 2 W + headers — iso
show(["Pico2W_Board", "Pico2W_Headers"])
save("comp-pico-iso.png")

# Piezo speaker — iso
show(["Piezo_Brass", "Piezo_Ceramic"])
save("comp-piezo-iso.png")

# IMU module — iso
show(["IMU_Module"])
save("comp-imu-iso.png")

# Solar panel — iso (bottom view)
show(["Solar_Frame", "Solar_Cells", "Solar_Wire_Plus", "Solar_Wire_Minus"])
view_bottom()
save("comp-solar-bottom.png", axometric=False, fit=False)
save("comp-solar-iso.png")

# TP4056 charger — iso
show(["TP4056_Module"])
save("comp-tp4056-iso.png")

# Batteries + clips — iso
show(["AAA_Battery_1", "AAA_Battery_1_PosTerm",
      "AAA_Battery_2", "AAA_Battery_2_PosTerm",
      "BatteryClips_Positive", "BatteryClips_Negative",
      "BatteryWiring_Positive", "BatteryWiring_Negative"])
save("comp-batteries-iso.png")

# Display — iso
show(["EInkDisplay_Module", "EInkDisplay_Panel"])
save("comp-display-iso.png")

print(f"\nDone — renders saved to {RENDER_DIR}")
App.closeDocument(doc.Name)
