"""
Dilder Rev 2 -- TRUE Parametric FreeCAD Model (PartDesign)
==========================================================
Builds all 3 parts using real PartDesign features:
  Sketcher constraints, Pads, Pockets, Fillets, Additive/Subtractive primitives.

Every feature appears in the Model tree. Double-click any sketch to edit
its geometry. Change any value in the Parameters spreadsheet and hit
recompute (Ctrl+Shift+R) -- the entire model updates.

Usage:
  FreeCAD > Macro > Run Macro > select this file
"""

import math
import FreeCAD as App
import Part
import Sketcher

V = App.Vector
ROT0 = App.Rotation()

# =====================================================================
# HELPERS
# =====================================================================

def find_edges(feature, axis=None, z_near=None, z_max=None):
    """Find edge names by orientation or position."""
    results = []
    for i, e in enumerate(feature.Shape.Edges):
        verts = e.Vertexes
        if len(verts) != 2:
            continue
        p1, p2 = verts[0].Point, verts[1].Point
        if axis == "vertical":
            if abs(p1.x - p2.x) < 0.01 and abs(p1.y - p2.y) < 0.01 and abs(p1.z - p2.z) > 0.5:
                results.append(f"Edge{i + 1}")
        elif axis == "horizontal_bottom":
            mid_z = (p1.z + p2.z) / 2
            if abs(p1.z - p2.z) < 0.01 and mid_z < 0.5:
                results.append(f"Edge{i + 1}")
    return results


# =====================================================================
# PARAMETER SPREADSHEET
# =====================================================================

PARAMS = [
    # (alias, value, description)
    # --- Enclosure ---
    ("enc_x",       94.5,  "Enclosure width X"),
    ("enc_y",       46.0,  "Enclosure depth Y"),
    ("wall_mx",      3.0,  "-X wall thickness"),
    ("wall_px",      1.2,  "+X wall thickness"),
    ("wall_y",       2.0,  "Side wall thickness Y"),
    ("corner_r",     4.0,  "Corner radius"),
    ("pillar",       5.0,  "Corner pillar side"),
    # --- Base plate ---
    ("bp_h",         8.0,  "Base plate height Z"),
    ("bp_fillet",    2.0,  "Bottom fillet radius"),
    ("bp_floor",     2.5,  "Pocket floor thickness"),
    # --- Cradle pocket ---
    ("cpx0",         3.1,  "Pocket X start"),
    ("cpx1",        93.2,  "Pocket X end"),
    ("cpy0",         2.1,  "Pocket Y start"),
    ("cpy1",        43.9,  "Pocket Y end"),
    # --- Pegs ---
    ("peg_d",        3.0,  "Peg diameter"),
    ("peg_h",        3.0,  "Peg height above plate"),
    ("peg_cham",     0.4,  "Peg tip chamfer"),
    # --- Pillar extensions ---
    ("ext_x",        5.0,  "Pillar extension X"),
    ("ext_y",        4.0,  "Pillar extension Y"),
    ("ext_z",       -1.5,  "Extension Z above plate"),
    # --- Battery troughs ---
    ("bay_d",       11.1,  "AAA bay diameter"),
    ("bay_yM",       7.85, "Bay -Y center"),
    ("bay_yP",      38.15, "Bay +Y center"),
    ("bay_xs",      34.0,  "Trough X start"),
    ("bay_xl",      39.0,  "Trough X length"),
    ("rail_lift",    5.0,  "Rail Z lift"),
    ("rail_hred",    2.5,  "Rail height reduce"),
    ("rail_dred",    2.0,  "Rail depth reduce"),
    # --- USB-C ---
    ("usb_w",        9.2,  "USB-C cutout width"),
    ("usb_h",        4.45, "USB-C cutout height"),
    ("usb_zd",       0.5,  "USB-C Z drop"),
    # --- Solar ---
    ("sol_x",       62.4,  "Solar pit width"),
    ("sol_y",       36.4,  "Solar pit depth"),
    ("sol_z",        2.0,  "Solar pit Z depth"),
    ("sol_hd",       3.1,  "Solar hole diameter"),
    ("sol_h1x",      2.5,  "Hole 1 X in pit"),
    ("sol_h1y",      2.0,  "Hole 1 Y in pit"),
    ("sol_h2x",     60.0,  "Hole 2 X in pit"),
    ("sol_h2y",      2.4,  "Hole 2 Y in pit"),
    # --- USB support blocks ---
    ("ublk_xs",      5.0,  "USB block X size"),
    ("ublk_yw",     15.0,  "USB block Y width"),
    ("ublk_gap",     5.0,  "USB block gap"),
    ("ublk_inset",   5.0,  "USB block inset from wall"),
    # --- Pico retention ---
    ("pblk_inset",  18.0,  "Pico block inset from -X"),
    ("pblk_xs",      5.0,  "Pico block X size"),
    ("pblk_yw",     15.0,  "Pico block Y width"),
    ("pblk_zh",      2.0,  "Pico block Z height"),
    # --- Cradle ---
    ("plug_slop",    0.3,  "Plug wall slop"),
    ("aaa_d",       10.5,  "AAA cell diameter"),
    ("aaa_rslop",    0.3,  "AAA radial slop"),
    ("aaa_bwall",    0.5,  "Bay wall above/below"),
    ("aaa_len",     44.5,  "AAA cell length"),
    ("aaa_aslop",    1.0,  "AAA axial slop"),
    ("aaa_cspace",   2.0,  "Contact space per end"),
    ("pil_cslop",    0.4,  "Pillar cutout slop"),
    ("fpc_gap",      3.0,  "FPC gap width"),
    ("pico_by",     21.0,  "Pico board width Y"),
    ("pico_bx",     78.0,  "Pico board length X"),
    ("fit_tol",      0.4,  "Print fit tolerance"),
    ("conn_xl",     29.0,  "Connecting block X length"),
    ("tp_xl",       28.0,  "TP4056 board X"),
    ("tp_yw",       17.0,  "TP4056 board Y"),
    ("tp_iz",        1.0,  "TP4056 indent depth"),
    ("tp_slop",      0.2,  "TP4056 slop"),
    ("disp_cz",      3.0,  "Display cutout depth Z"),
    ("clip_sz",      7.0,  "Clip plate size"),
    ("clip_tk",      0.5,  "Clip plate thickness"),
    ("clip_slop",    0.2,  "Clip slot slop"),
    ("clip_ret",     1.0,  "Retainer thickness"),
    ("clip_win",     5.0,  "Retainer window size"),
    # --- Top cover ---
    ("tc_bull",      4.0,  "Bullnose radius"),
    ("tc_fp_z",      0.7,  "Face plate thickness"),
    ("tc_wext",      5.0,  "Wall ext below mating"),
    ("disp_xl",     65.0,  "Display length X"),
    ("disp_yd",     30.0,  "Display depth Y"),
    ("disp_z",       7.0,  "Display thickness Z"),
    ("inlay_z",      3.0,  "Screen inlay depth"),
    ("inlay_slop",   0.3,  "Inlay XY slop"),
    ("inlay_yslop",  0.35, "Inlay Y slop"),
    ("win_xl",      48.0,  "Window length X"),
    ("win_yd",      22.0,  "Window depth Y"),
    ("win_shift",    2.8,  "Window shift X"),
    ("joy_d",       12.0,  "Joystick hole diameter"),
    ("joy_cx",      79.35, "Joystick center X"),
    ("m3_d",         3.2,  "M3 bore diameter"),
    ("joy_px",      20.0,  "Joystick PCB X"),
    ("joy_py",      20.0,  "Joystick PCB Y"),
    ("fpc_dy",      13.0,  "FPC divet width Y"),
    ("fpc_dw",       1.0,  "FPC divet wall remain"),
    ("fpc_dze",      2.0,  "FPC divet Z extend"),
]


def setup_spreadsheet(doc):
    if hasattr(doc, "Parameters"):
        sheet = doc.Parameters
    else:
        sheet = doc.addObject("Spreadsheet::Sheet", "Parameters")
    sheet.set("A1", "Parameter")
    sheet.set("B1", "Value")
    sheet.set("C1", "Description")
    for i, (alias, val, desc) in enumerate(PARAMS, start=2):
        cell = f"B{i}"
        sheet.set(f"A{i}", alias)
        sheet.set(cell, str(val))
        sheet.set(f"C{i}", desc)
        try:
            sheet.setAlias(cell, alias)
        except Exception:
            pass
    doc.recompute()
    return sheet


def SP(alias):
    """Expression string referencing a spreadsheet parameter."""
    return f"Parameters.{alias}"


# =====================================================================
# BASE PLATE
# =====================================================================

def build_base_plate(doc):
    print("  Building Base Plate...")
    body = doc.addObject("PartDesign::Body", "BasePlate")

    # -- 1. Outline sketch on XY plane --
    sk = body.newObject("Sketcher::SketchObject", "Sk_Outline")
    sk.AttachmentSupport = [(body.Origin.OriginFeatures[3], "")]  # XY
    sk.MapMode = "FlatFace"

    W, H = 94.5, 46.0
    sk.addGeometry(Part.LineSegment(V(0, 0, 0), V(W, 0, 0)), False)
    sk.addGeometry(Part.LineSegment(V(W, 0, 0), V(W, H, 0)), False)
    sk.addGeometry(Part.LineSegment(V(W, H, 0), V(0, H, 0)), False)
    sk.addGeometry(Part.LineSegment(V(0, H, 0), V(0, 0, 0)), False)
    sk.addConstraint(Sketcher.Constraint("Coincident", 0, 2, 1, 1))
    sk.addConstraint(Sketcher.Constraint("Coincident", 1, 2, 2, 1))
    sk.addConstraint(Sketcher.Constraint("Coincident", 2, 2, 3, 1))
    sk.addConstraint(Sketcher.Constraint("Coincident", 3, 2, 0, 1))
    sk.addConstraint(Sketcher.Constraint("Horizontal", 0))
    sk.addConstraint(Sketcher.Constraint("Horizontal", 2))
    sk.addConstraint(Sketcher.Constraint("Vertical", 1))
    sk.addConstraint(Sketcher.Constraint("Vertical", 3))
    sk.addConstraint(Sketcher.Constraint("Coincident", 0, 1, -1, 1))  # fix at origin
    c_w = sk.addConstraint(Sketcher.Constraint("DistanceX", 0, 1, 0, 2, W))
    c_h = sk.addConstraint(Sketcher.Constraint("DistanceY", 1, 1, 1, 2, H))
    sk.setExpression(f"Constraints[{c_w}]", SP("enc_x"))
    sk.setExpression(f"Constraints[{c_h}]", SP("enc_y"))
    doc.recompute()

    # -- 2. Pad shell --
    pad = body.newObject("PartDesign::Pad", "Pad_Shell")
    pad.Profile = sk
    pad.Length = 8.0
    pad.setExpression("Length", SP("bp_h"))
    doc.recompute()

    # -- 3. Fillet vertical edges (corner rounding) --
    vert_edges = find_edges(pad, axis="vertical")
    if vert_edges:
        fil_c = body.newObject("PartDesign::Fillet", "Fillet_Corners")
        fil_c.Base = (pad, vert_edges)
        fil_c.Radius = 4.0
        fil_c.setExpression("Radius", SP("corner_r"))
        doc.recompute()
        last_feat = fil_c
    else:
        last_feat = pad

    # -- 4. Fillet bottom horizontal edges --
    bot_edges = find_edges(last_feat, axis="horizontal_bottom")
    if bot_edges:
        fil_b = body.newObject("PartDesign::Fillet", "Fillet_Bottom")
        fil_b.Base = (last_feat, bot_edges)
        fil_b.Radius = 2.0
        fil_b.setExpression("Radius", SP("bp_fillet"))
        doc.recompute()
        last_feat = fil_b

    # -- 5. Cradle pocket -- SubtractiveBox from top (no sketch needed)
    cpx0, cpy0 = 3.1, 2.1
    cpx1, cpy1 = 93.2, 43.9
    pocket_depth = 8.0 - 2.5  # bp_h - bp_floor = 5.5
    pock = body.newObject("PartDesign::SubtractiveBox", "Pocket_Cradle")
    pock.Length = cpx1 - cpx0
    pock.Width = cpy1 - cpy0
    pock.Height = pocket_depth
    pock.Placement = App.Placement(V(cpx0, cpy0, 8.0 - pocket_depth), ROT0)
    pock.setExpression("Length", SP("cpx1") + " - " + SP("cpx0"))
    pock.setExpression("Width", SP("cpy1") + " - " + SP("cpy0"))
    pock.setExpression("Height", SP("bp_h") + " - " + SP("bp_floor"))
    doc.recompute()

    # -- 6. USB-C cutout on +X face -- rounded (stadium) shape, open at top
    # USB-C connector is a rounded rectangle. We open the top edge so the
    # connector can slide in from above (or so wires route out the top).
    #
    # Built from 3 subtractive features:
    #   - Main box: full width, from corner_r above bottom to past plate top
    #   - Bottom strip: narrower (width - 2*r), fills the flat bottom between corners
    #   - 2 cylinders: round the two bottom corners
    uw = 9.2       # usb_w
    usb_r = 1.0    # USB-C corner radius
    usb_z_bot = 8.0 - 4.45 - 0.5  # bp_h - usb_h - usb_zd
    usb_y_center = H / 2
    wall_cut_len = 3.0  # cuts through the 1.2mm +X wall with margin

    # Main box: full width, from r above bottom to well past plate top (open top)
    usb_main = body.newObject("PartDesign::SubtractiveBox", "USB_Main")
    usb_main.Length = wall_cut_len
    usb_main.Width = uw
    usb_main.Height = 8.0 - usb_z_bot + 1.0  # extends past plate top
    usb_main.Placement = App.Placement(
        V(W - 1.5, usb_y_center - uw / 2, usb_z_bot + usb_r), ROT0)
    usb_main.setExpression("Width", SP("usb_w"))
    doc.recompute()

    # Bottom strip: narrower box between the two corner arcs
    usb_bot = body.newObject("PartDesign::SubtractiveBox", "USB_Bottom")
    usb_bot.Length = wall_cut_len
    usb_bot.Width = uw - 2 * usb_r  # 7.2mm (inside the two corner radii)
    usb_bot.Height = usb_r
    usb_bot.Placement = App.Placement(
        V(W - 1.5, usb_y_center - (uw - 2 * usb_r) / 2, usb_z_bot), ROT0)
    doc.recompute()

    # Two cylinders for the rounded bottom corners
    for side, y_off in [("L", usb_y_center - uw / 2 + usb_r),
                        ("R", usb_y_center + uw / 2 - usb_r)]:
        cyl = body.newObject("PartDesign::SubtractiveCylinder", f"USB_Corner_{side}")
        cyl.Radius = usb_r
        cyl.Height = wall_cut_len
        cyl.Placement = App.Placement(
            V(W - 1.5, y_off, usb_z_bot + usb_r),
            App.Rotation(V(0, 1, 0), 90))
        doc.recompute()

    # -- 7. Solar pit on bottom face -- SubtractiveBox (cuts upward from z=0)
    sol_x, sol_y, sol_z = 62.4, 36.4, 2.0
    sx0 = W / 2 - sol_x / 2
    sy0 = H / 2 - sol_y / 2
    sol_cut = body.newObject("PartDesign::SubtractiveBox", "Cut_SolarPit")
    sol_cut.Length = sol_x
    sol_cut.Width = sol_y
    sol_cut.Height = sol_z
    sol_cut.Placement = App.Placement(V(sx0, sy0, 0), ROT0)
    sol_cut.setExpression("Length", SP("sol_x"))
    sol_cut.setExpression("Width", SP("sol_y"))
    sol_cut.setExpression("Height", SP("sol_z"))
    doc.recompute()

    # -- 8. Wire holes -- SubtractiveCylinder (vertical, from bottom)
    hole_r = 3.1 / 2
    for hi, (hx_off, hy_off) in enumerate([(2.5, 2.0), (60.0, 2.4)]):
        hole = body.newObject("PartDesign::SubtractiveCylinder", f"WireHole_{hi+1}")
        hole.Radius = hole_r
        hole.Height = 8.2  # through all (bp_h + margin)
        hole.Placement = App.Placement(V(sx0 + hx_off, sy0 + hy_off, -0.1), ROT0)
        hole.setExpression("Radius", SP("sol_hd") + " / 2")
        doc.recompute()

    # -- 9. Corner pillars (4 additive boxes) --
    ps = 5.0
    floor_z = 2.5
    plate_h = 8.0
    peg_positions = [
        (3.0 + ps / 2,          2.0 + ps / 2),
        (94.5 - 1.2 - ps / 2,   2.0 + ps / 2),
        (3.0 + ps / 2,          46.0 - 2.0 - ps / 2),
        (94.5 - 1.2 - ps / 2,   46.0 - 2.0 - ps / 2),
    ]
    center_x, center_y = 94.5 / 2, 46.0 / 2

    for i, (px, py) in enumerate(peg_positions):
        is_mx = px < center_x
        is_my = py < center_y

        # 5x5 pillar
        pil = body.newObject("PartDesign::AdditiveBox", f"Pillar_{i+1}")
        pil.Length = ps
        pil.Width = ps
        pil.Height = plate_h - floor_z
        pil.Placement = App.Placement(V(px - ps/2, py - ps/2, floor_z), ROT0)
        pil.setExpression("Length", SP("pillar"))
        pil.setExpression("Width", SP("pillar"))
        pil.setExpression("Height", SP("bp_h") + " - " + SP("bp_floor"))
        doc.recompute()

        # Extension wing
        ext_x, ext_y = 5.0, 4.0
        wx = (px - ps/2) if is_mx else (px - ps/2 - ext_x)
        wy = (py - ps/2) if is_my else (py - ps/2 - ext_y)
        wh = plate_h + (-1.5) - floor_z
        if wh > 0:
            wing = body.newObject("PartDesign::AdditiveBox", f"Wing_{i+1}")
            wing.Length = ps + ext_x
            wing.Width = ps + ext_y
            wing.Height = wh
            wing.Placement = App.Placement(V(wx, wy, floor_z), ROT0)
            wing.setExpression("Height", SP("bp_h") + " + " + SP("ext_z") + " - " + SP("bp_floor"))
            doc.recompute()

        # Peg (cylinder above plate top)
        peg = body.newObject("PartDesign::AdditiveCylinder", f"Peg_{i+1}")
        peg.Radius = 1.5
        peg.Height = 3.0
        peg.Placement = App.Placement(V(px, py, plate_h), ROT0)
        peg.setExpression("Radius", SP("peg_d") + " / 2")
        peg.setExpression("Height", SP("peg_h"))
        doc.recompute()

    # -- 10. Battery troughs --
    bay_r = 11.1 / 2
    bay_cz = plate_h + 0.95  # 8.95 in assembly = 8.95 in body (body at Z=0)
    rail_lift = 5.0
    for idx, (bay_y, is_plus) in enumerate([(7.85, False), (38.15, True)]):
        if is_plus:
            fy0 = bay_y - bay_r - 0.1 + 2.0
            fy1 = 46.0 - 2.0
        else:
            fy0 = 2.0
            fy1 = bay_y + bay_r + 0.1 - 2.0

        rz_bot = floor_z + rail_lift
        fz_top = plate_h - 2.5 + rail_lift

        # Support block
        sup = body.newObject("PartDesign::AdditiveBox", f"RailSupport_{idx+1}")
        sup.Length = 39.0
        sup.Width = fy1 - fy0
        sup.Height = rail_lift + 0.1
        sup.Placement = App.Placement(V(34.0, fy0, floor_z), ROT0)
        sup.setExpression("Length", SP("bay_xl"))
        sup.setExpression("Height", SP("rail_lift") + " + 0.1")
        doc.recompute()

        # Rail body
        rail = body.newObject("PartDesign::AdditiveBox", f"RailBody_{idx+1}")
        rail.Length = 39.0
        rail.Width = fy1 - fy0
        rail.Height = fz_top - rz_bot + 0.1
        rail.Placement = App.Placement(V(34.0, fy0, rz_bot), ROT0)
        rail.setExpression("Length", SP("bay_xl"))
        doc.recompute()

        # Subtract battery cylinder
        # Cylinder axis along X (rotate 90deg around Y)
        # Center at (bay_xs, bay_y, bay_cz + rail_lift) in body coords
        cyl_cz = bay_cz + rail_lift  # 8.95 + 5.0 = 13.95
        cyl = body.newObject("PartDesign::SubtractiveCylinder", f"BayCut_{idx+1}")
        cyl.Radius = bay_r
        cyl.Height = 39.2
        cyl.Placement = App.Placement(
            V(34.0 - 0.1, bay_y, cyl_cz),
            App.Rotation(V(0, 1, 0), 90))
        cyl.setExpression("Radius", SP("bay_d") + " / 2")
        cyl.setExpression("Height", SP("bay_xl") + " + 0.2")
        doc.recompute()

    # -- 11. USB support blocks --
    bx0 = 94.5 - 5.0 - 2 * 5.0
    by0 = 46.0 / 2 - 15.0 / 2
    bz_h = (plate_h - 4.45 - 0.5) - floor_z
    for j, offset in enumerate([0, -(5.0 + 5.0)]):
        blk = body.newObject("PartDesign::AdditiveBox", f"USBBlock_{j+1}")
        blk.Length = 5.0
        blk.Width = 15.0
        blk.Height = max(0.1, bz_h)
        blk.Placement = App.Placement(V(bx0 + offset, by0, floor_z), ROT0)
        blk.setExpression("Width", SP("ublk_yw"))
        blk.setExpression("Length", SP("ublk_xs"))
        doc.recompute()

    # -- 12. Pico retention block --
    prb = body.newObject("PartDesign::AdditiveBox", "PicoBlock")
    prb.Length = 5.0
    prb.Width = 15.0
    prb.Height = 2.0
    prb.Placement = App.Placement(V(3.0 + 18.0, 46.0/2 - 15.0/2, floor_z), ROT0)
    prb.setExpression("Length", SP("pblk_xs"))
    prb.setExpression("Width", SP("pblk_yw"))
    prb.setExpression("Height", SP("pblk_zh"))
    doc.recompute()

    print(f"    Base Plate: {body.Shape.Faces.__len__()} faces, "
          f"{len([o for o in body.Group if 'Sketch' not in o.TypeId])} features")
    return body


# =====================================================================
# AAA CRADLE
# =====================================================================

def build_cradle(doc):
    print("  Building AAA Cradle...")
    body = doc.addObject("PartDesign::Body", "AAACradle")

    # Derived dims
    bay_d = 10.5 + 2 * 0.3  # 11.1
    plug_thick = bay_d + 2 * 0.5  # 12.1
    plug_top = 7.0
    plug_bot = plug_top - plug_thick  # -5.1
    plug_x0, plug_x1 = 3.3, 93.0
    plug_y0, plug_y1 = 2.3, 43.7
    bay_len = 44.5 + 2*2.0 + 1.0  # 49.5
    bay_px_end = 69.9
    bay_mx_start = bay_px_end - bay_len  # 20.4
    bay_cz = (plug_top + plug_bot) / 2  # ~0.95

    # -- 1. Main plug body --
    sk = body.newObject("Sketcher::SketchObject", "Sk_Plug")
    sk.AttachmentSupport = [(body.Origin.OriginFeatures[3], "")]
    sk.MapMode = "FlatFace"
    sk.AttachmentOffset = App.Placement(V(0, 0, plug_bot), ROT0)

    pw, ph = plug_x1 - plug_x0, plug_y1 - plug_y0
    sk.addGeometry(Part.LineSegment(V(plug_x0, plug_y0, 0), V(plug_x1, plug_y0, 0)), False)
    sk.addGeometry(Part.LineSegment(V(plug_x1, plug_y0, 0), V(plug_x1, plug_y1, 0)), False)
    sk.addGeometry(Part.LineSegment(V(plug_x1, plug_y1, 0), V(plug_x0, plug_y1, 0)), False)
    sk.addGeometry(Part.LineSegment(V(plug_x0, plug_y1, 0), V(plug_x0, plug_y0, 0)), False)
    sk.addConstraint(Sketcher.Constraint("Coincident", 0, 2, 1, 1))
    sk.addConstraint(Sketcher.Constraint("Coincident", 1, 2, 2, 1))
    sk.addConstraint(Sketcher.Constraint("Coincident", 2, 2, 3, 1))
    sk.addConstraint(Sketcher.Constraint("Coincident", 3, 2, 0, 1))
    sk.addConstraint(Sketcher.Constraint("Horizontal", 0))
    sk.addConstraint(Sketcher.Constraint("Horizontal", 2))
    sk.addConstraint(Sketcher.Constraint("Vertical", 1))
    sk.addConstraint(Sketcher.Constraint("Vertical", 3))
    c_xo = sk.addConstraint(Sketcher.Constraint("DistanceX", -1, 1, 0, 1, plug_x0))
    c_yo = sk.addConstraint(Sketcher.Constraint("DistanceY", -1, 1, 0, 1, plug_y0))
    c_pw = sk.addConstraint(Sketcher.Constraint("DistanceX", 0, 1, 0, 2, pw))
    c_ph = sk.addConstraint(Sketcher.Constraint("DistanceY", 1, 1, 1, 2, ph))
    doc.recompute()

    pad = body.newObject("PartDesign::Pad", "Pad_Plug")
    pad.Profile = sk
    pad.Length = plug_thick
    doc.recompute()

    # -- 2. Corner pillar cutouts --
    ps = 5.0
    slop = 0.4
    cs = ps + 2 * slop
    pillar_origins = [
        (3.0, 2.0), (94.5 - 1.2 - ps, 2.0),
        (3.0, 46.0 - 2.0 - ps), (94.5 - 1.2 - ps, 46.0 - 2.0 - ps),
    ]
    for i, (ox, oy) in enumerate(pillar_origins):
        cut = body.newObject("PartDesign::SubtractiveBox", f"PillarCut_{i+1}")
        cut.Length = cs
        cut.Width = cs
        cut.Height = plug_thick + 0.2
        cut.Placement = App.Placement(V(ox - slop, oy - slop, plug_bot - 0.1), ROT0)
        doc.recompute()

    # -- 3. FPC gap --
    fpc = body.newObject("PartDesign::SubtractiveBox", "FPC_Gap")
    fpc.Length = 3.1
    fpc.Width = plug_y1 - plug_y0 + 0.2
    fpc.Height = plug_thick + 0.2
    fpc.Placement = App.Placement(V(plug_x0 - 0.1, plug_y0 - 0.1, plug_bot - 0.1), ROT0)
    fpc.setExpression("Length", SP("fpc_gap") + " + 0.1")
    doc.recompute()

    # -- 4. Battery bays (2 subtractive cylinders + 2 top-open boxes) --
    for j, bay_y in enumerate([7.85, 38.15]):
        cyl = body.newObject("PartDesign::SubtractiveCylinder", f"BatteryBay_{j+1}")
        cyl.Radius = bay_d / 2
        cyl.Height = bay_len + 0.2
        cyl.Placement = App.Placement(
            V(bay_mx_start - 0.1, bay_y, bay_cz),
            App.Rotation(V(0, 1, 0), 90))
        cyl.setExpression("Radius", "(" + SP("aaa_d") + " + 2 * " + SP("aaa_rslop") + ") / 2")
        doc.recompute()

        # Top-open slot
        slot = body.newObject("PartDesign::SubtractiveBox", f"BaySlot_{j+1}")
        slot.Length = bay_len + 0.2
        slot.Width = bay_d
        slot.Height = plug_top + 0.1 - bay_cz
        slot.Placement = App.Placement(
            V(bay_mx_start - 0.1, bay_y - bay_d/2, bay_cz), ROT0)
        doc.recompute()

    # -- 5. Pico nest --
    pico_ny = 21.0 + 2 * 0.4
    pico_nx = 78.0 + 2 * 0.4
    pico_y_start = 46.0 / 2 - pico_ny / 2
    pico_x_start = max(plug_x0 + 3.0,
        ((plug_x0 + 3.0 + bay_mx_start) / 2 - pico_nx / 2))
    nest = body.newObject("PartDesign::SubtractiveBox", "PicoNest")
    nest.Length = pico_nx
    nest.Width = pico_ny
    nest.Height = plug_thick + 0.2
    nest.Placement = App.Placement(V(pico_x_start, pico_y_start, plug_bot - 0.1), ROT0)
    doc.recompute()

    # -- 6. -X inset (cleared for connecting block) --
    inset = body.newObject("PartDesign::SubtractiveBox", "MinusX_Inset")
    inset.Length = 29.0
    inset.Width = pico_ny
    inset.Height = plug_thick + 0.1
    inset.Placement = App.Placement(V(plug_x0, pico_y_start, plug_bot), ROT0)
    inset.setExpression("Length", SP("conn_xl"))
    doc.recompute()

    # -- 7. +X display connector cutout --
    disp_cut = body.newObject("PartDesign::SubtractiveBox", "DispCutout")
    disp_cut.Length = plug_x1 - bay_px_end + 0.1
    disp_cut.Width = pico_ny
    disp_cut.Height = 3.1
    disp_cut.Placement = App.Placement(V(bay_px_end, pico_y_start, plug_bot - 0.1), ROT0)
    disp_cut.setExpression("Height", SP("disp_cz") + " + 0.1")
    doc.recompute()

    # -- 8. Connecting block (additive box with subtractions) --
    conn = body.newObject("PartDesign::AdditiveBox", "ConnBlock")
    conn.Length = 29.0
    conn.Width = pico_ny
    conn.Height = plug_thick
    conn.Placement = App.Placement(V(plug_x0, pico_y_start, plug_bot), ROT0)
    conn.setExpression("Length", SP("conn_xl"))
    doc.recompute()

    # Battery arcs through connecting block
    for j, bay_y in enumerate([7.85, 38.15]):
        arc = body.newObject("PartDesign::SubtractiveCylinder", f"ConnArc_{j+1}")
        arc.Radius = bay_d / 2
        arc.Height = 29.2
        arc.Placement = App.Placement(
            V(plug_x0 - 0.1, bay_y, bay_cz),
            App.Rotation(V(0, 1, 0), 90))
        doc.recompute()

    # TP4056 indent
    tp_len = 28.0 + 2 * 0.2
    tp_wid = 17.0 + 2 * 0.2
    tp_y = (pico_y_start + pico_y_start + pico_ny) / 2 - tp_wid / 2
    tp_indent = body.newObject("PartDesign::SubtractiveBox", "TP4056_Indent")
    tp_indent.Length = tp_len
    tp_indent.Width = tp_wid
    tp_indent.Height = 1.1
    tp_indent.Placement = App.Placement(V(plug_x0, tp_y, plug_top - 1.0), ROT0)
    tp_indent.setExpression("Height", SP("tp_iz") + " + 0.1")
    doc.recompute()

    # -- 9. Battery clip slots (4) --
    clip_slot_y = 7.0 + 2 * 0.2  # 7.4
    clip_slot_x = 0.5 + 2 * 0.2  # 0.9
    ret_thick = 1.0
    for j, bay_y in enumerate([7.85, 38.15]):
        for bay_x, is_plus in [(bay_mx_start, False), (bay_px_end, True)]:
            sx = (bay_x + ret_thick if is_plus
                  else bay_x - clip_slot_x - ret_thick)
            sy = bay_y - clip_slot_y / 2
            sz_bot = bay_cz - 7.0/2 - 0.2
            slot = body.newObject("PartDesign::SubtractiveBox",
                                  f"ClipSlot_{j*2 + (1 if is_plus else 0) + 1}")
            slot.Length = clip_slot_x
            slot.Width = clip_slot_y
            slot.Height = plug_top + 0.1 - sz_bot
            slot.Placement = App.Placement(V(sx, sy, sz_bot), ROT0)
            doc.recompute()

            # Retainer window
            wx = (bay_x - 0.1 if is_plus
                  else bay_x - ret_thick - 0.1)
            wy = bay_y - 5.0 / 2
            wz = bay_cz - 5.0 / 2
            win = body.newObject("PartDesign::SubtractiveBox",
                                 f"ClipWin_{j*2 + (1 if is_plus else 0) + 1}")
            win.Length = ret_thick + 0.2
            win.Width = 5.0
            win.Height = 5.0
            win.Placement = App.Placement(V(wx, wy, wz), ROT0)
            win.setExpression("Width", SP("clip_win"))
            win.setExpression("Height", SP("clip_win"))
            doc.recompute()

    print(f"    Cradle: {len(body.Shape.Faces)} faces")
    return body


# =====================================================================
# TOP COVER
# =====================================================================

def build_top_cover(doc):
    print("  Building Top Cover...")
    body = doc.addObject("PartDesign::Body", "TopCover")

    enc_x, enc_y = 94.5, 46.0
    wall_mx = 3.0
    wall_px = 1.2
    wall_y = 2.0
    face_bot = 7.0
    fp_z = 0.7
    face_top = face_bot + fp_z  # 7.7
    bull_r = 4.0
    total_h = face_top + bull_r  # 11.7
    ext = 5.0

    # -- 1. Outer shell sketch + pad --
    sk = body.newObject("Sketcher::SketchObject", "Sk_Shell")
    sk.AttachmentSupport = [(body.Origin.OriginFeatures[3], "")]
    sk.MapMode = "FlatFace"
    sk.AttachmentOffset = App.Placement(V(0, 0, -ext), ROT0)

    sk.addGeometry(Part.LineSegment(V(0, 0, 0), V(enc_x, 0, 0)), False)
    sk.addGeometry(Part.LineSegment(V(enc_x, 0, 0), V(enc_x, enc_y, 0)), False)
    sk.addGeometry(Part.LineSegment(V(enc_x, enc_y, 0), V(0, enc_y, 0)), False)
    sk.addGeometry(Part.LineSegment(V(0, enc_y, 0), V(0, 0, 0)), False)
    sk.addConstraint(Sketcher.Constraint("Coincident", 0, 2, 1, 1))
    sk.addConstraint(Sketcher.Constraint("Coincident", 1, 2, 2, 1))
    sk.addConstraint(Sketcher.Constraint("Coincident", 2, 2, 3, 1))
    sk.addConstraint(Sketcher.Constraint("Coincident", 3, 2, 0, 1))
    sk.addConstraint(Sketcher.Constraint("Horizontal", 0))
    sk.addConstraint(Sketcher.Constraint("Horizontal", 2))
    sk.addConstraint(Sketcher.Constraint("Vertical", 1))
    sk.addConstraint(Sketcher.Constraint("Vertical", 3))
    sk.addConstraint(Sketcher.Constraint("Coincident", 0, 1, -1, 1))
    c_w = sk.addConstraint(Sketcher.Constraint("DistanceX", 0, 1, 0, 2, enc_x))
    c_h = sk.addConstraint(Sketcher.Constraint("DistanceY", 1, 1, 1, 2, enc_y))
    sk.setExpression(f"Constraints[{c_w}]", SP("enc_x"))
    sk.setExpression(f"Constraints[{c_h}]", SP("enc_y"))
    doc.recompute()

    pad = body.newObject("PartDesign::Pad", "Pad_Shell")
    pad.Profile = sk
    pad.Length = total_h + ext
    pad.setExpression("Length", SP("tc_fp_z") + " + " + SP("tc_bull") + " + " +
                      SP("disp_z") + " + " + SP("tc_wext"))
    doc.recompute()

    # -- 2. Fillet corners --
    vert_edges = find_edges(pad, axis="vertical")
    if vert_edges:
        fil = body.newObject("PartDesign::Fillet", "Fillet_Corners")
        fil.Base = (pad, vert_edges)
        fil.Radius = 4.0
        fil.setExpression("Radius", SP("corner_r"))
        doc.recompute()

    # -- 3. Fillet top edges (bullnose) --
    tip = body.Tip
    top_edges = []
    for i, e in enumerate(tip.Shape.Edges):
        v = e.Vertexes
        if len(v) == 2:
            p1, p2 = v[0].Point, v[1].Point
            mz = (p1.z + p2.z) / 2
            if abs(p1.z - p2.z) < 0.01 and mz > total_h - 1:
                top_edges.append(f"Edge{i+1}")
    if top_edges:
        fil_top = body.newObject("PartDesign::Fillet", "Fillet_Bullnose")
        fil_top.Base = (tip, top_edges)
        fil_top.Radius = 4.0
        fil_top.setExpression("Radius", SP("tc_bull"))
        doc.recompute()

    # -- 4. Interior cavity -- SubtractiveBox
    # In body-local coords: from z=-ext to z=face_bot => height = face_bot + ext = 12
    cav_x0 = wall_mx           # 3.0
    cav_x1 = enc_x - wall_px   # 93.3
    cav_y0 = wall_y             # 2.0
    cav_y1 = enc_y - wall_y    # 44.0
    cav_z_bot = -ext            # -5.0
    cav_h = face_bot + ext      # 12.0

    cav = body.newObject("PartDesign::SubtractiveBox", "Cut_Cavity")
    cav.Length = cav_x1 - cav_x0
    cav.Width = cav_y1 - cav_y0
    cav.Height = cav_h
    cav.Placement = App.Placement(V(cav_x0, cav_y0, cav_z_bot), ROT0)
    cav.setExpression("Length", SP("enc_x") + " - " + SP("wall_mx") + " - " + SP("wall_px"))
    cav.setExpression("Width", SP("enc_y") + " - 2 * " + SP("wall_y"))
    cav.setExpression("Height", SP("disp_z") + " + " + SP("tc_wext"))
    doc.recompute()

    # -- 5. Corner pillars (additive, inside cavity) --
    ps = 5.0
    pillar_origins = [
        (3.0, 2.0), (enc_x - 1.2 - ps, 2.0),
        (3.0, enc_y - 2.0 - ps), (enc_x - 1.2 - ps, enc_y - 2.0 - ps),
    ]
    for i, (ox, oy) in enumerate(pillar_origins):
        pil = body.newObject("PartDesign::AdditiveBox", f"CoverPillar_{i+1}")
        pil.Length = ps
        pil.Width = ps
        pil.Height = face_bot + ext  # fill from -ext to face_bot
        pil.Placement = App.Placement(V(ox, oy, -ext), ROT0)
        pil.setExpression("Length", SP("pillar"))
        pil.setExpression("Width", SP("pillar"))
        doc.recompute()

    # -- 6. Screen inlay pocket -- SubtractiveBox
    # Inlay: cut from face_bot - inlay_z to face_bot => z=4.0 to 7.0, height=3
    disp_x0 = wall_mx + 0.4     # 3.4
    disp_x1 = disp_x0 + 65.0    # 68.4
    disp_y0 = enc_y / 2 - 30.0 / 2  # 8.0
    disp_y1 = disp_y0 + 30.0    # 38.0
    inlay_x0 = disp_x0 - 0.3    # 3.1
    inlay_x1 = disp_x1 + 0.3    # 68.7
    inlay_y0 = disp_y0 - 0.35   # 7.65
    inlay_y1 = disp_y1 + 0.35   # 38.35
    inlay_z_depth = 3.0
    inlay_z_bot = face_bot - inlay_z_depth  # 4.0

    inlay = body.newObject("PartDesign::SubtractiveBox", "Cut_Inlay")
    inlay.Length = inlay_x1 - inlay_x0
    inlay.Width = inlay_y1 - inlay_y0
    inlay.Height = inlay_z_depth
    inlay.Placement = App.Placement(V(inlay_x0, inlay_y0, inlay_z_bot), ROT0)
    inlay.setExpression("Height", SP("inlay_z"))
    doc.recompute()

    # -- 7. Display window (through face plate + dome) -- SubtractiveBox
    # Window cuts from face_bot to total_h
    win_w = 48.0
    win_h = 22.0
    win_x0 = disp_x0 + (65.0 - win_w) / 2 + 2.8  # shifted
    win_y0 = disp_y0 + (30.0 - win_h) / 2
    win_z_height = total_h - face_bot + 0.2  # through face plate and dome

    win = body.newObject("PartDesign::SubtractiveBox", "Cut_Window")
    win.Length = win_w
    win.Width = win_h
    win.Height = win_z_height
    win.Placement = App.Placement(V(win_x0, win_y0, face_bot - 0.1), ROT0)
    win.setExpression("Length", SP("win_xl"))
    win.setExpression("Width", SP("win_yd"))
    doc.recompute()

    # -- 8. Joystick hole -- SubtractiveCylinder (vertical, through top)
    joy_cx = 79.35
    joy_cy = enc_y / 2
    joy_r = 12.0 / 2
    joy_cut_h = total_h - face_bot + 0.2

    joy = body.newObject("PartDesign::SubtractiveCylinder", "Cut_Joystick")
    joy.Radius = joy_r
    joy.Height = joy_cut_h
    joy.Placement = App.Placement(V(joy_cx, joy_cy, face_bot - 0.1), ROT0)
    joy.setExpression("Radius", SP("joy_d") + " / 2")
    doc.recompute()

    # -- 9. M3 screw bores through pillars -- SubtractiveCylinder
    peg_pos = [
        (3.0 + ps/2, 2.0 + ps/2),
        (enc_x - 1.2 - ps/2, 2.0 + ps/2),
        (3.0 + ps/2, enc_y - 2.0 - ps/2),
        (enc_x - 1.2 - ps/2, enc_y - 2.0 - ps/2),
    ]
    for i, (px, py) in enumerate(peg_pos):
        bore = body.newObject("PartDesign::SubtractiveCylinder", f"M3Bore_{i+1}")
        bore.Radius = 3.2 / 2
        bore.Height = face_bot + ext + 0.2
        bore.Placement = App.Placement(V(px, py, -ext - 0.1), ROT0)
        bore.setExpression("Radius", SP("m3_d") + " / 2")
        doc.recompute()

    # -- 10. Joystick PCB pocket -- SubtractiveBox
    # Cut from face_bot - 3 to face_bot
    joy_pcb_x0 = inlay_x1        # 68.7
    joy_pcb_y0 = enc_y / 2 - 20.0 / 2  # 3.0
    joy_pcb_w = 20.0
    joy_pcb_h = 20.0
    joy_pcb_depth = 3.0

    jpcb = body.newObject("PartDesign::SubtractiveBox", "Cut_JoyPCB")
    jpcb.Length = joy_pcb_w
    jpcb.Width = joy_pcb_h
    jpcb.Height = joy_pcb_depth
    jpcb.Placement = App.Placement(V(joy_pcb_x0, joy_pcb_y0, face_bot - joy_pcb_depth), ROT0)
    jpcb.setExpression("Length", SP("joy_px"))
    jpcb.setExpression("Width", SP("joy_py"))
    jpcb.setExpression("Height", SP("inlay_z"))
    doc.recompute()

    # -- 11. FPC ribbon divet -- SubtractiveBox
    # Cut from face_bot - (inlay_z + fpc_dze) to face_bot
    fpc_x0 = 1.0  # fpc_dw
    fpc_x1 = inlay_x0  # 3.1
    fpc_y0 = enc_y / 2 - 13.0 / 2
    fpc_y1 = fpc_y0 + 13.0
    fpc_depth = inlay_z_depth + 2.0  # 5.0

    fpc_cut = body.newObject("PartDesign::SubtractiveBox", "Cut_FPC")
    fpc_cut.Length = fpc_x1 - fpc_x0
    fpc_cut.Width = fpc_y1 - fpc_y0
    fpc_cut.Height = fpc_depth
    fpc_cut.Placement = App.Placement(V(fpc_x0, fpc_y0, face_bot - fpc_depth), ROT0)
    fpc_cut.setExpression("Width", SP("fpc_dy"))
    fpc_cut.setExpression("Height", SP("inlay_z") + " + " + SP("fpc_dze"))
    doc.recompute()

    print(f"    Top Cover: {len(body.Shape.Faces)} faces")
    return body


# =====================================================================
# MAIN
# =====================================================================

def main():
    doc_name = "Dilder_Rev2_PD"
    if App.ActiveDocument and App.ActiveDocument.Name == doc_name:
        App.closeDocument(doc_name)

    doc = App.newDocument(doc_name)
    print("Setting up spreadsheet...")
    setup_spreadsheet(doc)

    bp = build_base_plate(doc)
    cr = build_cradle(doc)
    tc = build_top_cover(doc)

    # Position cradle and cover in assembly
    cr.Placement = App.Placement(V(0, 0, 8.0), ROT0)
    tc.Placement = App.Placement(V(0, 0, 8.0), ROT0)

    # Colors
    if bp.ViewObject:
        bp.ViewObject.ShapeColor = (0.6, 0.65, 0.7)
    if cr.ViewObject:
        cr.ViewObject.ShapeColor = (0.9, 0.75, 0.4)
    if tc.ViewObject:
        tc.ViewObject.ShapeColor = (0.4, 0.55, 0.8)
        tc.ViewObject.Transparency = 40

    doc.recompute()
    print(f"\nDone! Feature tree:")
    for body_obj in [bp, cr, tc]:
        features = [o.Name for o in body_obj.Group if "Origin" not in o.Name]
        print(f"  {body_obj.Name}: {len(features)} features")
        for f in features:
            print(f"    - {f}")

    print(f"\nDouble-click any Sketch to edit geometry.")
    print(f"Change values in the Parameters spreadsheet, then Ctrl+Shift+R to recompute.")

    try:
        import FreeCADGui
        FreeCADGui.activeDocument().activeView().viewAxometric()
        FreeCADGui.SendMsgToActiveView("ViewFit")
    except Exception:
        pass

    return doc


if __name__ == "__main__" or True:
    main()
